MAP-OperationAndMaintenanceOperations {itu-t(0) identified-organization(4) etsi(0) mobileDomain(0) gsm-Network(1) modules(3) map-OperationAndMaintenanceOperations(6) version18(18)}

DEFINITIONS ::= BEGIN

	EXPORTS
		activateTraceMode,
		deactivateTraceMode,
		sendIMSI;

	IMPORTS
		OPERATION
	FROM Remote-Operations-Information-Objects
			{joint-iso-itu-t(2) remote-operations(4) informationObjects(5) version1(0)}
		systemFailure,
		dataMissing,
		unexpectedDataValue,
		facilityNotSupported,
		unknownSubscriber,
		unidentifiedSubscriber,
		tracingBufferFull
	FROM MAP-Errors
			{itu-t(0) identified-organization(4) etsi(0) mobileDomain(0) gsm-Network(1) modules(3) map-Errors(10) version18(18)}
		ActivateTraceModeArg,
		ActivateTraceModeRes,
		DeactivateTraceModeArg,
		DeactivateTraceModeRes
	FROM MAP-OM-DataTypes
			{itu-t(0) identified-organization(4) etsi(0) mobileDomain(0) gsm-Network(1) modules(3) map-OM-DataTypes(12) version18(18)}
		ISDN-AddressString,
		IMSI
	FROM MAP-CommonDataTypes
			{itu-t(0) identified-organization(4) etsi(0) mobileDomain(0) gsm-Network(1) modules(3) map-CommonDataTypes(18) version18(18)};

	activateTraceMode  OPERATION ::= {	--Timer m
		ARGUMENT
		ActivateTraceModeArg
		RESULT
		ActivateTraceModeRes
		-- optional
		ERRORS {
		systemFailure |
		dataMissing |
		unexpectedDataValue |
		facilityNotSupported |
		unidentifiedSubscriber |
		tracingBufferFull}
		CODE	local:50 }

	deactivateTraceMode  OPERATION ::= {	--Timer m
		ARGUMENT
		DeactivateTraceModeArg
		RESULT
		DeactivateTraceModeRes
		-- optional
		ERRORS {
		systemFailure |
		dataMissing |
		unexpectedDataValue |
		facilityNotSupported |
		unidentifiedSubscriber}
		CODE	local:51 }

	sendIMSI  OPERATION ::= {	--Timer m
		ARGUMENT
		ISDN-AddressString
		RESULT
		IMSI
		ERRORS {
		dataMissing |
		unexpectedDataValue |
		unknownSubscriber}
		CODE	local:58 }

END
